FME workspace WebDavTransformer.fmw

Parameters:
- MKCOL =
- SourceDataset_PATH =

Readers:
- PATH_1: PATH from $(SourceDataset_PATH)

Note: WebDav Copy file
WebDav_6
    BASEURI = https://staging-datashare.devel5cph.eionet.europa.eu/remote.php/dav/files/bliki/
    COPY_FROM_PATH = mynewfolder/trial.pdf
    COPY_OVERWRITE = T
    COPY_TO_PATH = trial2.pdf
    GROUP_COPY = YES
    GROUP_CREATE_FOLDER = NO
    GROUP_DELETE = NO
    GROUP_DOWNLOAD_FILE = NO
    GROUP_LIST = NO
    GROUP_MOVE = NO
    GROUP_UPLOAD_FILE = NO
    HTTP_CALL_TRANSFER_TIMEOUT = 60
    HTTP_CLIENT_CONN_TIMEOUT = 60
    HTTP_CLIENT_VERIFY_SSL = Yes
    WEBDAV_CONN = janbliki HTTP EIONET Authentication
Note: WebDav Move file
WebDav_7
    BASEURI = https://staging-datashare.devel5cph.eionet.europa.eu/remote.php/dav/files/bliki/
    GROUP_COPY = NO
    GROUP_CREATE_FOLDER = NO
    GROUP_DELETE = NO
    GROUP_DOWNLOAD_FILE = NO
    GROUP_LIST = NO
    GROUP_MOVE = YES
    GROUP_UPLOAD_FILE = NO
    HTTP_CALL_TRANSFER_TIMEOUT = 60
    HTTP_CLIENT_CONN_TIMEOUT = 60
    HTTP_CLIENT_VERIFY_SSL = Yes
    MOVE_FROM_PATH = trial.pdf
    MOVE_OVERWRITE = T
    MOVE_TO_PATH = mynewfolder/trial.pdf
    WEBDAV_CONN = janbliki HTTP EIONET Authentication
Creator
    GEOMTYPE = Geometry Object
    NUM = 1
    CREATED -> WebDav_3
Note: WebDav assign Tags
WebDav_3
    BASEURI = https://staging-datashare.devel5cph.eionet.europa.eu/remote.php/dav/files/bliki/
    GROUP_COPY = NO
    GROUP_CREATE_FOLDER = NO
    GROUP_DELETE = NO
    GROUP_DOWNLOAD_FILE = NO
    GROUP_LIST = NO
    GROUP_MOVE = NO
    GROUP_PROPERTY = YES
    GROUP_UPLOAD_FILE = NO
    HTTP_CALL_TRANSFER_TIMEOUT = 60
    HTTP_CLIENT_CONN_TIMEOUT = 60
    HTTP_CLIENT_VERIFY_SSL = Yes
    PROP_FAVORITE = YES
    PROP_PATH_ITEM = trial.pdf
    WEBDAV_CONN = janbliki HTTP EIONET Authentication

Bookmark: DEMO FILES UPLOAD
PATH (reader PATH_1) [off]
    attributes: path_unix buffer, path_windows buffer, path_rootname buffer, path_filename buffer, path_extension buffer, path_filesize number(20,0), path_ownername buffer, path_readonly logical, path_modified_date datetime, path_created_date datetime, path_accessed_date datetime, path_directory_unix buffer, path_directory_windows buffer, path_type char(10)
    -> AttributeRemover
Note: Create/Delete folder
WebDav_8
    BASEURI = https://staging-datashare.devel5cph.eionet.europa.eu/remote.php/dav/files/bliki/
    CREATE_FOLDER_PATH = @Value(path_directory_windows)
    DELETE_PATH = @Value(path_directory_delete)
    GROUP_COPY = NO
    GROUP_CREATE_FOLDER = YES
    GROUP_DELETE = YES
    GROUP_DOWNLOAD_FILE = NO
    GROUP_LIST = NO
    GROUP_MOVE = NO
    GROUP_PROPERTY = NO
    GROUP_UPLOAD_FILE = NO
    HTTP_CALL_TRANSFER_TIMEOUT = 60
    HTTP_CLIENT_CONN_TIMEOUT = 60
    HTTP_CLIENT_VERIFY_SSL = No
    WEBDAV_CONN = janbliki HTTP EIONET Authentication
    <rejected> -> WebDav_8__rejected__2
WebDav_8__rejected__2: Inspector
Note: Create files
WebDav_9
    BASEURI = https://staging-datashare.devel5cph.eionet.europa.eu/remote.php/dav/files/bliki/
    GROUP_COPY = NO
    GROUP_CREATE_FOLDER = NO
    GROUP_DELETE = NO
    GROUP_DOWNLOAD_FILE = NO
    GROUP_LIST = NO
    GROUP_MOVE = NO
    GROUP_PROPERTY = NO
    GROUP_UPLOAD_FILE = YES
    HTTP_CALL_TRANSFER_TIMEOUT = 60
    HTTP_CLIENT_CONN_TIMEOUT = 60
    HTTP_CLIENT_VERIFY_SSL = Yes
    UPLOAD_FILE_DESTINATION = @Value(root_webdav)
    UPLOAD_FILE_SOURCE = @Value(path_windows)
    WEBDAV_CONN = janbliki HTTP EIONET Authentication
    <rejected> -> WebDav_9__rejected_
WebDav_9__rejected_: Inspector

Bookmark: PREPARE PATH TO WebDav
AttributeRemover
    REMOVE_ATTRS = path_accessed_date,path_created_date,path_directory_unix,path_filesize,path_modified_date,path_ownername,path_readonly,path_type,path_unix
    -> AttributeCreator_3
AttributeCreator_3
    ATTR_TABLE = SET_TO root_webdav = FMETest
    -> StringReplacer
Note: Remove windows path / \\Users\\janbliki\\Documents\\FME\
StringReplacer
    CASE = NO
    FIND_TEXT = (\\Users\\janbliki\\Documents\\FME\\|\\$)
    NO_MATCH = _FME_NO_OP_
    REGEXP = YES
    SRC_ATTRS = path_directory_windows
    -> StringReplacer_3
Note: Replace \ with /
StringReplacer_3
    CASE = NO
    FIND_TEXT = \
    NO_MATCH = _FME_NO_OP_
    REGEXP = NO
    REPLACE_TEXT = /
    SRC_ATTRS = path_directory_windows
    -> Aggregator
    -> FeatureHolder
Aggregator
    ACCUM_ATTRS_NAME = Drop Incoming Attributes
    AGGREGATE_TYPE = Homogeneous Collection (If Possible)
    GROUP_BY = path_directory_windows root_webdav
    MODE = Geometry - Assemble One Level
    SEP = ,
    AGGREGATE -> Sampler
    AGGREGATE -> Sorter
Sampler
    RATE = 1
    SAMPLE_MODE = No
    SAMPLE_TYPE_LONG = First N Features
    SAMPLED -> AttributeCreator_6
AttributeCreator_6
    ATTR_TABLE:
      SET_TO path_directory_windows = @Value(root_webdav)
      SET_TO path_directory_delete = @Value(root_webdav)
    -> Junction
Sorter
    SORT_PARM = path_directory_windows ALPHA ASCENDING
    SORTED -> AttributeCreator_7
AttributeCreator_7
    ATTR_TABLE = SET_TO path_directory_windows = @Value(root_webdav)/@Value(path_directory_windows)
    -> Junction
Note: Folders Input
Junction
    -> WebDav_8
FeatureHolder
    -> AttributeCreator_4
Note: Create WebDav_path
AttributeCreator_4
    ATTR_TABLE = SET_TO root_webdav = @Value(root_webdav)/@Value(path_directory_windows)/@Value(path_filename)
    -> WebDav_9

Bookmark: DEMO DOWNLOAD FILES
Note: https://staging-datashare.devel5cph.eionet.europa.eu/remote.php/dav/files/bliki/
Note: KroJ2-csoY2-rQmek-N7AQ9-kE7jk / FME / bliki
Creator_3 [off]
    GEOMTYPE = Geometry Object
    NUM = 1
    CREATED -> WebDav_2
Note: List folder
WebDav_2
    BASEURI = https://staging-datashare.devel5cph.eionet.europa.eu/remote.php/dav/files/bliki/
    GROUP_COPY = NO
    GROUP_CREATE_FOLDER = NO
    GROUP_DELETE = NO
    GROUP_DOWNLOAD_FILE = NO
    GROUP_LIST = YES
    GROUP_MOVE = NO
    GROUP_PROPERTY = NO
    GROUP_UPLOAD_FILE = NO
    HTTP_CALL_TRANSFER_TIMEOUT = 60
    HTTP_CLIENT_CONN_TIMEOUT = 60
    HTTP_CLIENT_VERIFY_SSL = Yes
    LIST_FOLDER_PATH = Photos
    LIST_ONLY_FOLDER = NO
    LIST_PROPERTIES = "<oc:fileid />" "<d:getlastmodified />" "<oc:owner-display-name />" "<d:getcontenttype />" "<oc:size />"
    WEBDAV_CONN = janbliki HTTP EIONET Authentication
    -> TestFilter
TestFilter
    DEFAULT_VALUE = File
    TEST_LIST = "BOOL_OP,OR,COMPOSITE_TEST,""""""1"""""",TEST_CLAUSE,CASE_INSENSITIVE_TEST @Value(webdav_href) ENDS_WITH /",Folder
    Folder -> WebDav_12
    File -> WebDav_11
Note: List folder Level 2
WebDav_12
    BASEURI = https://staging-datashare.devel5cph.eionet.europa.eu/remote.php/dav/files/bliki/
    GROUP_COPY = NO
    GROUP_CREATE_FOLDER = NO
    GROUP_DELETE = NO
    GROUP_DOWNLOAD_FILE = NO
    GROUP_LIST = YES
    GROUP_MOVE = NO
    GROUP_PROPERTY = NO
    GROUP_UPLOAD_FILE = NO
    HTTP_CALL_TRANSFER_TIMEOUT = 60
    HTTP_CLIENT_CONN_TIMEOUT = 60
    HTTP_CLIENT_VERIFY_SSL = Yes
    LIST_FOLDER_PATH = @Value(webdav_href)
    LIST_ONLY_FOLDER = NO
    LIST_PROPERTIES = "<oc:fileid />" "<d:getlastmodified />" "<oc:owner-display-name />" "<d:getcontenttype />" "<oc:size />"
    WEBDAV_CONN = janbliki HTTP EIONET Authentication
    -> TestFilter_2
TestFilter_2
    DEFAULT_VALUE = File
    TEST_LIST = "BOOL_OP,OR,COMPOSITE_TEST,""""""1"""""",TEST_CLAUSE,CASE_INSENSITIVE_TEST @Value(webdav_href) ENDS_WITH /",Folder
    File -> WebDav_11
Note: Download files
WebDav_11
    BASEURI = https://staging-datashare.devel5cph.eionet.europa.eu/remote.php/dav/files/bliki/
    DOWNLOAD_FILE_FROM_PATH = @Value(webdav_href)
    DOWNLOAD_FILE_LOCAL_PATH = ./@Value(webdav_href)
    GROUP_COPY = NO
    GROUP_CREATE_FOLDER = NO
    GROUP_DELETE = NO
    GROUP_DOWNLOAD_FILE = YES
    GROUP_LIST = NO
    GROUP_MOVE = NO
    GROUP_PROPERTY = NO
    GROUP_UPLOAD_FILE = NO
    HTTP_CALL_TRANSFER_TIMEOUT = 60
    HTTP_CLIENT_CONN_TIMEOUT = 60
    HTTP_CLIENT_VERIFY_SSL = Yes
    WEBDAV_CONN = janbliki HTTP EIONET Authentication

FME custom transformer webdavErrorExtractor

Parameters:
- XMLContent =

XMLFlattener_Input (input)
    -> ParameterFetcher
ParameterFetcher
    ATTR_LIST = _XMLContent $(XMLContent)
    -> XMLFlattener
XMLFlattener
    ATTRIBUTE_XML = _XMLContent
    EMBEDDED_EXPRESSIONS = /error/message
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = message
    XML_SOURCE_TYPE = Attribute with XML document
    -> AttributeRenamer
    <REJECTED> -> <Rejected> (output)
AttributeRenamer
    ATTR_TABLE = RENAME_SET_DEFAULT message > _error
    MISSING_INPUT_ATTRS = REMOVE
    -> Output (output)
Output (output)
<Rejected> (output)

FME custom transformer WebDavCounter

Parameters:
- COUNTER_NAME_FAILED =
- COUNTER_NAME_SUCCESS =
- XML_MESSAGE =

Success (input)
    -> AttributeCreator_8
Note: Counter
AttributeCreator_8
    ATTR_TABLE = SET_TO $(COUNTER_NAME_SUCCESS) = @Count($(COUNTER_NAME_SUCCESS),1)
    -> Sampler_2
Sampler_2
    RATE = 1
    SAMPLE_MODE = No
    SAMPLE_TYPE_LONG = Last N Features
    SAMPLED -> Success (output)
Success (output)
Failed (input)
    -> AttributeCreator_2
    -> ParameterFetcher
Note: Counter
AttributeCreator_2
    ATTR_TABLE = SET_TO $(COUNTER_NAME_FAILED) = @Count($(COUNTER_NAME_FAILED),1)
    -> Sampler_3
Sampler_3
    RATE = 1
    SAMPLE_MODE = No
    SAMPLE_TYPE_LONG = Last N Features
    SAMPLED -> Failed (output)
Failed (output)
ParameterFetcher
    ATTR_LIST = _XML_MESSAGE $(XML_MESSAGE)
    -> webdavErrorExtractor [XMLFlattener_Input]
webdavErrorExtractor
    XMLContent = @Value(_XML_MESSAGE)
    -> ExtractedError (output)
    <Rejected> -> ExtractedError (output)
ExtractedError (output)

FME custom transformer WebDav
WebDav and NextCloud filesystem over HTTP(S) Access
Allows users to connect to a WebDav/NextCloud REST API. You can perform actions without first mapping to a file system.  Ideal for FME Server implementations.
This code is based on documentation I found on the NextCloud help
WARNING: This has only been tested on a NextCloud instance.
Webdav configuration:
Base uri : The URI to the webdav root folder.  (For NextCoud this looks like https://myserver.com/remote.php/dav/files/)
Web connection: The FME named web connection.  Use basic web authentication.  Nextcloud allows an API user implementation.  In that case you use the user name that has created they key and the unique key as password.
Every group in the GUI-interfact represent a WebDav command. You are allowed to use multiple commands in one instance.  The execution sequence of these commands follow the interface.  They will be executed from top to bottom. For example you can delete a file on NextCloud before you upload a new version. 
Delete file or folder
Delete a single file or an entire folder. This will execute recursive and delete all sub-folders and files as well.
Path to item: The folder or file to be deleted.  (always provide the full path) 
Create folder:
Create a new folder on the WebDav service.  
Folder path: provide the path to the folder.  (always provide the full path) 
http_status_code have specific applicabilities.  
201 (Created) - The collection was created. 
403 (Forbidden) - This indicates at least one of two conditions: 1) the server does not allow the creation of collections at the given location in its URL namespace, or 2) the parent collection of the Request-URI exists but cannot accept members.
405 (Method Not Allowed) - MKCOL can only be executed on an unmapped URL. 
409 (Conflict) - A collection cannot be made at the Request-URI until one or more intermediate collections have been created.  The server MUST NOT create those intermediate collections automatically. 
415 (Unsupported Media Type) - The server does not support the request body type (although bodies are legal on MKCOL requests, since this specification doesn't define any, the server is likely not to support any given body type). 
507 (Insufficient Storage) - The resource does not have sufficient space to record the state of the resource after the execution of this method.
Upload file:
Upload single file to WebDav
Select a file: Path to the local file.
Destination path: The file name on WebDav.  (always provide the full path) 
Move file or folder
Move a file or folder on WebDav
From path: The file/folder that needs to be moved.
To path: The file/folder where it should be stored. 
Copy file or folder
Copy a file or folder on WebDav
From path: The file/folder that needs to be moved.  (always provide the full path)
To path: The file/folder where it should be stored.  (always provide the full path)
List folder
List content structure from WebDav.
Folder path: The folder on WebDav you like to list. Provide nothing if you want to scan from the root.
Meta properties: The properties you wish to retrieve.
Folder properties only: When checked only the specified folder properties will be retrieved and not it's content.
Download file
Download a file from WebDav to a local file system.
From path: The filename on WebDav.  (always provide the full path)
Local file path: The full path and file name on the local file system.
Outputs
Output: 
All successfull features will pass throught the output. Only LIST, DOWNLOAD and UPLOAD will provide additional parameters.  We concider the request successfull if the http_status_code returns equal or bugger to 200 but less or equal to 299 
http_status_codes is only returned for LIST, DOWNLOAD and UPLOAD actions.
Summary:
Summary provides you counts of all successfull and failed actions.  We aggregate all results to one single feature.
:
Those actions that generated an error on the WebDav are channeled through .  An _error attribute will return information given by the WebDav service.  A _resonse_body attribute that comes back from the HTTP request. This contains the XML from WebDav or NextCloud untouched.  _http_status_code will return the returned status code.  When we use the HTTPCaller an additional fme_rejection_code is returned.

Parameters:
- BASEURI =
- COPY_FROM_PATH =
- COPY_OVERWRITE =
- COPY_TO_PATH =
- CREATE_FOLDER_PATH =
- DELETE_PATH =
- DOWNLOAD_FILE_FROM_PATH =
- DOWNLOAD_FILE_LOCAL_PATH =
- GROUP_CONFIG =
- GROUP_COPY =
- GROUP_CREATE_FOLDER =
- GROUP_DELETE =
- GROUP_DOWNLOAD_FILE =
- GROUP_LIST =
- GROUP_MOVE =
- GROUP_PROPERTY =
- GROUP_UPLOAD_FILE =
- HTTP_CALL_TRANSFER_TIMEOUT =
- HTTP_CLIENT_CONN_TIMEOUT =
- HTTP_CLIENT_VERIFY_SSL =
- LIST_FOLDER_PATH =
- LIST_ONLY_FOLDER =
- LIST_PROPERTIES =
- MOVE_FROM_PATH =
- MOVE_OVERWRITE =
- MOVE_TO_PATH =
- PARAMETER =
- PROP_ETAGS =
- PROP_FAVORITE =
- PROP_PATH_ITEM =
- UPLOAD_FILE_DESTINATION =
- UPLOAD_FILE_SOURCE =
- WEBDAV_CONN =

AttributeKeeper
    CREATE_BULK_MODE_FEATURES = NO
    KEEP_ATTRS = Webdav.counter.upload_failed,Webdav.counter.upload_success,Webdav.counter.delete_failed,Webdav.counter.delete_success,Webdav.counter.create_folder_success,Webdav.counter.download_failed,Webdav.counter.download_success,Webdav.counter.move_failed,Webdav.counter.move_success,Webdav.counter.copy_failed,Webdav.counter.copy_success,Webdav.counter.list_failed,Webdav.counter.list_success
    -> Aggregator
Aggregator
    ACCUM_ATTRS_NAME = Use Attributes From One Feature
    AGGREGATE_TYPE = Homogeneous Collection (If Possible)
    MODE = Geometry - Assemble One Level
    SEP = ,
    SUM = Webdav.counter.upload_failed Webdav.counter.upload_success Webdav.counter.delete_failed Webdav.counter.delete_success Webdav.counter.create_folder_success Webdav.counter.download_failed Webdav.counter.download_success Webdav.counter.move_failed Webdav.counter.move_success Webdav.counter.copy_failed Webdav.counter.copy_success Webdav.counter.list_failed Webdav.counter.list_success
    AGGREGATE -> summary (output)
summary (output)
<rejected> (output)
Note: NextCloud implementation / Major functionality is based on the WebDav protocol. / The API can be found here .
Note: This method allows users to use multiple actions in the same transformer.
Note: Go's to output
Junction
    -> Junction_2
Note: Connects to LIST,DOWNLOAD,UPLOAD AND INPUT (for single actions)
Junction_2
    -> Output (output)
Output (output)
ParameterFetcher_8
    ATTR_LIST = _PROP_FAVORITE $(PROP_FAVORITE) _PROP_ETAGS $(PROP_ETAGS) _PROP_PATH_ITEM $(PROP_PATH_ITEM) _BASEURI $(BASEURI)
    -> AttributeCreator_8
AttributeCreator_8
    ATTR_TABLE:
      SET_TO _prop_favoriteXML = FME_CONDITIONAL:DEFAULT_VALUE'<oc:favorite>0</oc:favorite>'BOOL_OP;OR;COMPOSITE_TEST;1;TEST @Value(_PROP_FAVORITE) = Yes'<oc:favorite>1</oc:favorite>'FME_NUM_CONDITIONS2___
      SET_TO _prop_tagXML = FME_CONDITIONAL:DEFAULT_VALUE'_FME_NO_OP_'BOOL_OP;OR;COMPOSITE_TEST;1;TEST _PROP_ETAGS ATTRIBUTE_HAS_A_VALUE _FME_BLANK_STRING_'<oc:etag>@Value(_PROP_ETAGS)</oc:etag>'FME_NUM_CONDITIONS2___
      SET_TO _prop_xml = <?xml version="1.0"?>
        <d:propertyupdate xmlns:d="DAV:" xmlns:oc="http://owncloud.org/ns">
          <d:set>
                <d:prop>
                    @Value(_prop_favoriteXML)
                    @Value(_prop_tagXML)
                </d:prop>
          </d:set>
        </d:propertyupdate>
    -> PyHTTPCaller_5
PyHTTPCaller_5
    AUTH_NAMED_CONNECTION = $(WEBDAV_CONN)
    CONNECTION_TIMEOUT_LENGTH = $(HTTP_CLIENT_CONN_TIMEOUT)
    ERROR_ATTR = _error
    FOLLOW_REDIRECTS = FOLLOW_WITH_GET
    HTTP_METHOD = PROPPATCH
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = @Value(_BASEURI)/@Value(_PROP_PATH_ITEM)
    TRANSFER_TIMEOUT_LENGTH = $(HTTP_CALL_TRANSFER_TIMEOUT)
    USE_COOKIES = No
    VERIFY_SSL_CERTIFICATES = $(HTTP_CLIENT_VERIFY_SSL)

Bookmark: GROUP PARAMETERS
Input (input)
    -> TestFilter
    -> TestFilter_2
    -> TestFilter_3
    -> TestFilter_4
    -> TestFilter_5
    -> TestFilter_6
    -> TestFilter_7
    -> TestFilter_8
    -> TestFilter_11
TestFilter
    DEFAULT_VALUE = <UNFILTERED>
    TEST_LIST = "BOOL_OP,OR,COMPOSITE_TEST,""""""1"""""",TEST_CLAUSE,TEST $(GROUP_DELETE) = YES",DELETE
    DELETE -> ParameterFetcher_3
TestFilter_2
    DEFAULT_VALUE = <UNFILTERED>
    TEST_LIST = "BOOL_OP,OR,COMPOSITE_TEST,""""""1"""""",TEST_CLAUSE,TEST $(GROUP_CREATE_FOLDER) = YES",CREATE FOLDER
    CREATE FOLDER -> ParameterFetcher_6
TestFilter_3
    DEFAULT_VALUE = <UNFILTERED>
    TEST_LIST = "BOOL_OP,OR,COMPOSITE_TEST,""""""1"""""",TEST_CLAUSE,TEST $(GROUP_UPLOAD_FILE) = YES",UPLOAD FILE
    UPLOAD FILE -> ParameterFetcher_2
TestFilter_4
    DEFAULT_VALUE = <UNFILTERED>
    TEST_LIST = "BOOL_OP,OR,COMPOSITE_TEST,""""""1"""""",TEST_CLAUSE,TEST $(GROUP_MOVE) = YES",MOVE
    MOVE -> ParameterFetcher_7
TestFilter_5
    DEFAULT_VALUE = <UNFILTERED>
    TEST_LIST = "BOOL_OP,OR,COMPOSITE_TEST,""""""1"""""",TEST_CLAUSE,TEST $(GROUP_COPY) = YES",COPY
    COPY -> ParameterFetcher_5
TestFilter_6
    DEFAULT_VALUE = <UNFILTERED>
    TEST_LIST = "BOOL_OP,OR,COMPOSITE_TEST,""""""1"""""",TEST_CLAUSE,TEST $(GROUP_LIST) = YES",LIST
    LIST -> ParameterFetcher_4
TestFilter_7
    DEFAULT_VALUE = <UNFILTERED>
    TEST_LIST = "BOOL_OP,OR,COMPOSITE_TEST,""""""1"""""",TEST_CLAUSE,TEST $(GROUP_DOWNLOAD_FILE) = YES",DOWNLOAD
    DOWNLOAD -> ParameterFetcher
TestFilter_8
    DEFAULT_VALUE = Ignore
    TEST_LIST:
      "BOOL_OP,AND,COMPOSITE_TEST,""""""1 AND 2 AND 3"""""",TEST_CLAUSE,TEST $(GROUP_DOWNLOAD_FILE) NOT_= YES
      TEST $(GROUP_UPLOAD_FILE) NOT_= YES
      TEST $(GROUP_LIST) NOT_= YES",InitiatorOutput
    InitiatorOutput -> Junction
TestFilter_11
    DEFAULT_VALUE = Ignore
    TEST_LIST = "BOOL_OP,AND,COMPOSITE_TEST,""""""1"""""",TEST_CLAUSE,TEST $(GROUP_PROPERTY) = YES",InitiatorOutput
    InitiatorOutput -> ParameterFetcher_8

Bookmark: DELETE FILE/FOLDER
ParameterFetcher_3
    ATTR_LIST = _DELETE_PATH $(DELETE_PATH)
    -> TestFilter_9
TestFilter_9
    DEFAULT_VALUE = Ignore
    TEST_LIST = "BOOL_OP,OR,COMPOSITE_TEST,""""""1"""""",TEST_CLAUSE,TEST _DELETE_PATH ATTRIBUTE_HAS_A_VALUE """,ValueExist
    ValueExist -> AttributeCreator_3
Note: Remove "/" from start and end of path
AttributeCreator_3
    ATTR_TABLE = SET_TO _DELETE_PATH = @ReplaceRegularExpression(@Value(_DELETE_PATH),(^/{0,}|/{0,}$),,caseSensitive=TRUE)
    -> HTTPCaller_3
HTTPCaller_3
    AUTH_METHOD = Web Connection
    AUTH_NAMED_CONNECTION = $(WEBDAV_CONN)
    CONNECTION_TIMEOUT_LENGTH = $(HTTP_CLIENT_CONN_TIMEOUT)
    ERROR_ATTR = _error
    FOLLOW_REDIRECTS = FOLLOW_WITH_GET
    HTTP_METHOD = DELETE
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(BASEURI)/$(DELETE_PATH)
    TRANSFER_TIMEOUT_LENGTH = $(HTTP_CALL_TRANSFER_TIMEOUT)
    UPLOAD_CONTENT_TYPE = Text (text/plain)
    UPLOAD_TYPE = Specify Upload Body
    USE_COOKIES = No
    VERIFY_SSL_CERTIFICATES = $(HTTP_CLIENT_VERIFY_SSL)
    -> WebDavCounter [Success]
    <REJECTED> -> WebDavCounter [Failed]
WebDavCounter
    COUNTER_NAME_FAILED = Webdav.counter.delete_failed
    COUNTER_NAME_SUCCESS = Webdav.counter.delete_success
    XML_MESSAGE = @Value(_response_body)
    Success -> AttributeKeeper
    Failed -> AttributeKeeper
    ExtractedError -> <rejected> (output)

Bookmark: CREATE FOLDER
ParameterFetcher_6
    ATTR_LIST = _CREATE_FOLDER_PATH $(CREATE_FOLDER_PATH) _BASEURI $(BASEURI)
    -> TestFilter_10
TestFilter_10
    DEFAULT_VALUE = Ignore
    TEST_LIST = "BOOL_OP,OR,COMPOSITE_TEST,""""""1"""""",TEST_CLAUSE,TEST _CREATE_FOLDER_PATH ATTRIBUTE_HAS_A_VALUE """,ValueExist
    ValueExist -> AttributeCreator_7
Note: Remove "/" from start and end of path
AttributeCreator_7
    ATTR_TABLE = SET_TO _CREATE_FOLDER_PATH = @ReplaceRegularExpression(@Value(_CREATE_FOLDER_PATH),(^/{0,}|/{0,}$),,caseSensitive=TRUE)
    -> PyHTTPCaller_2
PyHTTPCaller_2
    AUTH_NAMED_CONNECTION = $(WEBDAV_CONN)
    CONNECTION_TIMEOUT_LENGTH = $(HTTP_CLIENT_CONN_TIMEOUT)
    ERROR_ATTR = _error
    FOLLOW_REDIRECTS = FOLLOW_WITH_GET
    HTTP_METHOD = MKCOL
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = @Value(_BASEURI)/@Value(_CREATE_FOLDER_PATH)
    TRANSFER_TIMEOUT_LENGTH = $(HTTP_CALL_TRANSFER_TIMEOUT)
    USE_COOKIES = No
    VERIFY_SSL_CERTIFICATES = $(HTTP_CLIENT_VERIFY_SSL)
    -> WebDavCounter_2 [Success]
    <REJECTED> -> WebDavCounter_2 [Failed]
WebDavCounter_2
    COUNTER_NAME_FAILED = Webdav.counter.create_folder_failed
    COUNTER_NAME_SUCCESS = Webdav.counter.create_folder_success
    XML_MESSAGE = @Value(_response_body)
    Success -> AttributeKeeper
    Failed -> AttributeKeeper
    ExtractedError -> <rejected> (output)

Bookmark: UPLOAD FILE
ParameterFetcher_2
    ATTR_LIST = _UPLOAD_FILE_DESTINATION $(UPLOAD_FILE_DESTINATION) _UPLOAD_FILE_SOURCE $(UPLOAD_FILE_SOURCE)
    -> HTTPCaller_2
HTTPCaller_2
    AUTH_METHOD = Web Connection
    AUTH_NAMED_CONNECTION = $(WEBDAV_CONN)
    CONNECTION_TIMEOUT_LENGTH = $(HTTP_CLIENT_CONN_TIMEOUT)
    ERROR_ATTR = _error
    FOLLOW_REDIRECTS = FOLLOW_WITH_GET
    HTTP_METHOD = PUT
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(BASEURI)/@Value(_UPLOAD_FILE_DESTINATION)
    TRANSFER_TIMEOUT_LENGTH = $(HTTP_CALL_TRANSFER_TIMEOUT)
    UPLOAD_CONTENT_TYPE = Binary (application/octet-stream)
    UPLOAD_FILE = @Value(_UPLOAD_FILE_SOURCE)
    UPLOAD_TYPE = Upload From File
    USE_COOKIES = No
    VERIFY_SSL_CERTIFICATES = $(HTTP_CLIENT_VERIFY_SSL)
    -> AttributeRemover_4
    <REJECTED> -> WebDavCounter_3 [Failed]
AttributeRemover_4
    REMOVE_ATTRS = _response_body,_UPLOAD_FILE_DESTINATION,_UPLOAD_FILE_SOURCE
    -> AttributeCreator_4
AttributeCreator_4
    ATTR_TABLE = SET_TO webdav_href = $(UPLOAD_FILE_DESTINATION)
    -> Junction_2
    -> WebDavCounter_3 [Success]
WebDavCounter_3
    COUNTER_NAME_FAILED = Webdav.counter.upload_failed
    COUNTER_NAME_SUCCESS = Webdav.counter.upload_success
    XML_MESSAGE = @Value(_response_body)
    Success -> AttributeKeeper
    Failed -> AttributeKeeper
    ExtractedError -> <rejected> (output)

Bookmark: MOVE
ParameterFetcher_7
    ATTR_LIST = _MOVE_FROM_PATH $(MOVE_FROM_PATH) _MOVE_TO_PATH $(MOVE_TO_PATH) _MOVE_OVERWRITE $(MOVE_OVERWRITE) _BASEURI $(BASEURI)
    -> PyHTTPCaller_3
PyHTTPCaller_3
    AUTH_NAMED_CONNECTION = $(WEBDAV_CONN)
    CONNECTION_TIMEOUT_LENGTH = $(HTTP_CLIENT_CONN_TIMEOUT)
    CUSTOM_HEADERS = Destination;@Value(_BASEURI)/@Value(_MOVE_TO_PATH);Overwrite;@Value(_MOVE_OVERWRITE)
    ERROR_ATTR = _error
    FOLLOW_REDIRECTS = FOLLOW_WITH_GET
    HTTP_METHOD = MOVE
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = @Value(_BASEURI)/@Value(_MOVE_FROM_PATH)
    TRANSFER_TIMEOUT_LENGTH = $(HTTP_CALL_TRANSFER_TIMEOUT)
    USE_COOKIES = No
    VERIFY_SSL_CERTIFICATES = $(HTTP_CLIENT_VERIFY_SSL)
    -> WebDavCounter_4 [Success]
    <REJECTED> -> WebDavCounter_4 [Failed]
WebDavCounter_4
    COUNTER_NAME_FAILED = Webdav.counter.move_failed
    COUNTER_NAME_SUCCESS = Webdav.counter.move_success
    XML_MESSAGE = @Value(_response_body)
    Success -> AttributeKeeper
    Failed -> AttributeKeeper
    ExtractedError -> <rejected> (output)

Bookmark: COPY
ParameterFetcher_5
    ATTR_LIST = _COPY_FROM_PATH $(COPY_FROM_PATH) _COPY_TO_PATH $(COPY_TO_PATH) _COPY_OVERWRITE $(COPY_OVERWRITE) _BASEURI $(BASEURI)
    -> PyHTTPCaller_4
PyHTTPCaller_4
    AUTH_NAMED_CONNECTION = $(WEBDAV_CONN)
    CONNECTION_TIMEOUT_LENGTH = $(HTTP_CLIENT_CONN_TIMEOUT)
    CUSTOM_HEADERS = Destination;@Value(_BASEURI)/@Value(_COPY_TO_PATH);Overwrite;@Value(_COPY_OVERWRITE)
    ERROR_ATTR = _error
    FOLLOW_REDIRECTS = FOLLOW_WITH_GET
    HTTP_METHOD = COPY
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = @Value(_BASEURI)/@Value(_COPY_OVERWRITE)
    TRANSFER_TIMEOUT_LENGTH = $(HTTP_CALL_TRANSFER_TIMEOUT)
    USE_COOKIES = No
    VERIFY_SSL_CERTIFICATES = $(HTTP_CLIENT_VERIFY_SSL)
    -> WebDavCounter_5 [Success]
    <REJECTED> -> WebDavCounter_5 [Failed]
WebDavCounter_5
    COUNTER_NAME_FAILED = Webdav.counter.copy_failed
    COUNTER_NAME_SUCCESS = Webdav.counter.copy_success
    XML_MESSAGE = @Value(_response_body)
    Success -> AttributeKeeper
    Failed -> AttributeKeeper
    ExtractedError -> <rejected> (output)

Bookmark: LIST
ParameterFetcher_4
    ATTR_LIST = _LIST_PROPERTIES $(LIST_PROPERTIES) _LIST_FOLDER_PATH $(LIST_FOLDER_PATH) _BASEURI $(BASEURI)
    -> AttributeCreator
Note: Remove "/" from start and end of path
AttributeCreator
    ATTR_TABLE:
      SET_TO _LIST_ONLY_FOLDERS = $(LIST_ONLY_FOLDER)_
      SET_TO _HEADER_LIST = FME_CONDITIONAL:DEFAULT_VALUE''BOOL_OP;OR;COMPOSITE_TEST;1;TEST @Value(_LIST_ONLY_FOLDERS) = YES_'0'FME_NUM_CONDITIONS2___
      SET_TO _LIST_FOLDER_PATH = @ReplaceRegularExpression(@Value(_LIST_FOLDER_PATH),(^/{0,}|/{0,}$),,caseSensitive=TRUE)
    -> StringReplacer
PyHTTPCaller
    AUTH_NAMED_CONNECTION = $(WEBDAV_CONN)
    CONNECTION_TIMEOUT_LENGTH = $(HTTP_CLIENT_CONN_TIMEOUT)
    CUSTOM_HEADERS = Depth;@Value(_HEADER_LIST)
    ERROR_ATTR = _error
    FOLLOW_REDIRECTS = FOLLOW_WITH_GET
    HTTP_METHOD = PROPFIND
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = @Value(_BASEURI)/@Value(_LIST_FOLDER_PATH)
    TRANSFER_TIMEOUT_LENGTH = $(HTTP_CALL_TRANSFER_TIMEOUT)
    UPLOAD_BODY = @Value(_LIST_PROPERTIES)
    UPLOAD_CONTENT_TYPE = XML (application/xml)
    UPLOAD_TYPE = Specify Upload Body
    USE_COOKIES = No
    VERIFY_SSL_CERTIFICATES = $(HTTP_CLIENT_VERIFY_SSL)
    -> XMLFragmenter
    -> WebDavCounter_7 [Success]
    <REJECTED> -> WebDavCounter_7 [Failed]
Note: Get all items from XML
XMLFragmenter
    ATTRIBUTE_XML = _response_body
    EMBEDDED_EXPRESSIONS = response
    FEATURE_TYPES_FORMAT_NAME = XML
    FLATTEN_OPTIONS = <structure separator="." map-empty-elements="no" matched-prefix="attributes" matched-attributes="yes" cardinality="+{?}" structure-prefix="" child-position-attribute="" except-expression="" ui-mode="basic" matched-ancestor-attributes=""/>
    MERGE_ATTRS = Yes
    NEW_ATTRIBUTES = href
    REJECT_FEATURES_WITH_NO_FRAGMENTS = YES
    XML_SOURCE_TYPE = Attribute with XML document
    FRAGMENTS -> AttributeRemover_2
AttributeRemover_2
    REMOVE_ATTRS = xml_fragment,xml_id,xml_matched_element,xml_parent_child_pos,xml_parent_id,_HEADER_LIST,_LIST_PROPERTIES,_response_body,_LIST_ONLY_FOLDERS
    -> TextDecoder
TextDecoder
    DEST_ATTR = webdav_href
    ENCODING_TYPE = URL (Percent Encoding)
    STRING_TO_DECODE = @Value(href)
    -> Sampler
Sampler
    RATE = 1
    SAMPLE_MODE = No
    SAMPLE_TYPE_LONG = First N Features
    SAMPLED -> AttributeCreator_5
    NOT_SAMPLED -> VariableRetriever
AttributeRemover
    REMOVE_ATTRS = href,_LENGTH_FIRST_RECORD,_LIST_FOLDER_PATH
    -> Junction_2
WebDavCounter_7
    COUNTER_NAME_FAILED = Webdav.counter.list_failed
    COUNTER_NAME_SUCCESS = Webdav.counter.list_success
    XML_MESSAGE = @Value(_response_body)
    Success -> AttributeKeeper
    Failed -> AttributeKeeper
    ExtractedError -> <rejected> (output)

Bookmark: PROPERTIES
StringReplacer
    CASE = NO
    FIND_TEXT = "
    NO_MATCH = _FME_NO_OP_
    REGEXP = NO
    SRC_ATTRS = _LIST_PROPERTIES
    -> AttributeCreator_2
AttributeCreator_2
    ATTR_TABLE:
      SET_TO _LIST_PROPERTIES = <?xml version="1.0"?>
        <d:propfind  xmlns:d="DAV:" xmlns:oc="http://owncloud.org/ns" xmlns:nc="http://nextcloud.org/ns">
          <d:prop>
          @Value(_LIST_PROPERTIES)
          </d:prop>
        </d:propfind>
    -> PyHTTPCaller

Bookmark: GET ROOT PATH and REMOVE (First record)
AttributeCreator_5
    ATTR_TABLE = SET_TO _LENGTH_FIRST_RECORD = FME_CONDITIONAL:DEFAULT_VALUE'@StringLength(@Value(webdav_href))-@StringLength(@Value(_LIST_FOLDER_PATH))'BOOL_OP;OR;COMPOSITE_TEST;1;CASE_INSENSITIVE_TEST @Value(webdav_href) ENDS_WITH /'@Evaluate(@StringLength(@Value(webdav_href))-@StringLength(@Value(_LIST_FOLDER_PATH)))-1'FME_NUM_CONDITIONS2___
    -> VariableSetter
VariableSetter
    SCOPE = Local
    VALUE = @Value(_LENGTH_FIRST_RECORD)
    VARNAME = LENGTH_REMOVE
    -> SubstringExtractor_2
SubstringExtractor_2
    END = 10000
    RESULT_ATTR = webdav_href
    SRC_STRING = @Value(webdav_href)
    START = @Value(_LENGTH_FIRST_RECORD)
    -> AttributeRemover

Bookmark: REMOVE ROOT PATH FROM webdav_href
VariableRetriever
    SCOPE = Local
    VALUE_ATTR = _LENGTH_FIRST_RECORD
    VARNAME = LENGTH_REMOVE
    -> AttributeCreator_6
AttributeCreator_6
    ATTR_TABLE = SET_TO webdav_href = @Substring(@Value(webdav_href),@Value(_LENGTH_FIRST_RECORD),10000)
    -> AttributeRemover

Bookmark: DOWNLOAD FILE
ParameterFetcher
    ATTR_LIST = _DOWLOAD_FILE_FROM_PATH $(DOWNLOAD_FILE_FROM_PATH) _DOWLOAD_FILE_LOCAL_PATH $(DOWNLOAD_FILE_LOCAL_PATH)
    -> HTTPCaller
HTTPCaller
    AUTH_METHOD = Web Connection
    AUTH_NAMED_CONNECTION = $(WEBDAV_CONN)
    CONNECTION_TIMEOUT_LENGTH = $(HTTP_CLIENT_CONN_TIMEOUT)
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = $(BASEURI)/$(DOWNLOAD_FILE_FROM_PATH)
    TRANSFER_TIMEOUT_LENGTH = $(HTTP_CALL_TRANSFER_TIMEOUT)
    USE_COOKIES = No
    VERIFY_SSL_CERTIFICATES = $(HTTP_CLIENT_VERIFY_SSL)
    -> AttributeFileWriter
    -> WebDavCounter_6 [Success]
    <REJECTED> -> WebDavCounter_6 [Failed]
Note: Only when successfull we save the file...
AttributeFileWriter
    CHAR_ENCODING = fme-binary
    FILE_NAME = @Value(_DOWLOAD_FILE_LOCAL_PATH)
    OVERWRITE_FILE = Overwrite file
    SOURCE_ATTR = _response_body
    -> AttributeRenamer
AttributeRenamer
    ATTR_TABLE = RENAME_SET_DEFAULT _DOWLOAD_FILE_FROM_PATH > webdav_href
    MISSING_INPUT_ATTRS = REMOVE
    -> AttributeRemover_3
AttributeRemover_3
    REMOVE_ATTRS = _response_body,_DOWLOAD_FILE_LOCAL_PATH
    -> Junction_2
WebDavCounter_6
    COUNTER_NAME_FAILED = Webdav.counter.download_failed
    COUNTER_NAME_SUCCESS = Webdav.counter.download_success
    XML_MESSAGE = @Value(_response_body)
    Success -> AttributeKeeper
    Failed -> AttributeKeeper
    ExtractedError -> <rejected> (output)
